module ietf-l3sm-ins {
  yang-version 1.1;
  namespace "urn:ietf:params:xml:ns:yang:ietf-l3sm-ins";
  prefix l3-ins;

  import ietf-network-slice-types {
    prefix ietf-nst;
    reference
      "I-D.ietf-teas-ietf-network-slice-nbi-yang: A Yang Data
       Model for IETF Network Slice Operation";
  }
  import ietf-l3vpn-svc {
    prefix l3vpn-svc;
    reference
      "RFC 8299: YANG Data Model for L3VPN Service Delivery";
  }

  organization
    "IETF Traffic Engineering Architecture and Signaling (TEAS)
     Working Group";
  contact
    "WG Web:  <https://tools.ietf.org/wg/teas/>
     WG List:  <mailto:teas@ietf.org>

     Editor: Bo Wu
          <lana.wubo@huawei.com>
     Editor: Dhruv Dhody
          <dhruv.ietf@gmail.com>
     Editor: Reza Rokui
          <reza.rokui@nokia.com>
     Editor: Tarek Saad
          <tsaad@juniper.net>
     Author: Liuyan Han
          <hanliuyan@chinamobile.com>";
  description
    "This module contains a YANG module for the adding IETF network
     slicing properties to Layer 3 Service Model (L3SM).

     Copyright (c) 2022 IETF Trust and the persons identified as
     authors of the code.  All rights reserved.

     Redistribution and use in source and binary forms, with or
     without modification, is permitted pursuant to, and subject to
     the license terms contained in, the Revised BSD License set
     forth in Section 4.c of the IETF Trust's Legal Provisions
     Relating to IETF Documents
     (https://trustee.ietf.org/license-info).

     This version of this YANG module is part of RFC XXXX; see the
     RFC itself for full legal notices.";

  revision 2022-03-18 {
    description
      "Initial revision.";
    reference
      "RFC XXXX:  TBD";
  }

  /*
   * Augmentation to L3SM
   */

  augment "/l3vpn-svc:l3vpn-svc/l3vpn-svc:vpn-services"
        + "/l3vpn-svc:vpn-service" {
    description
      "L3SM augmented to include IETF Network slice properties";
    container ins {
      presence
        "Indicates L3 service to include IETF network slice
         attrinutes";
      description
        "Container to augment l3sm to IETF network slice";
      uses ietf-nst:ns-properties;
      uses ietf-nst:ns-slo-sle-policy;
      uses ietf-nst:status-params;
      container ns-endpoints {
        description
          "NS Endpoints.";
        list ns-endpoint {
          key "ep-id";
          uses ietf-nst:endpoint-param;
          uses ietf-nst:ns-match-criteria;
          leaf site-id {
            type leafref {
              path "/l3vpn-svc:l3vpn-svc/l3vpn-svc:sites"
                 + "/l3vpn-svc:site/l3vpn-svc:site-id";
            }
            description
              "reference to L3SM site";
          }
          description
            "List of endpoints in this slice.";
        }
      }
      uses ietf-nst:ns-connection;
    }
  }

  augment "/l3vpn-svc:l3vpn-svc/l3vpn-svc:sites/l3vpn-svc:site"
        + "/l3vpn-svc:site-network-accesses"
        + "/l3vpn-svc:site-network-access"
        + "/l3vpn-svc:vpn-attachment" {
    description
      "This augment is only valid for TE mapping of L3SM network-access
       to TE endpoints";
    uses ietf-nst:ep-network-access-param;
    uses ietf-nst:ns-match-criteria;
  }
}
