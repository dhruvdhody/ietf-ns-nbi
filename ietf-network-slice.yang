module ietf-network-slice {
  yang-version 1.1;
  namespace "urn:ietf:params:xml:ns:yang:ietf-network-slice";
  prefix ietf-ns;

  import ietf-network-slice-types {
    prefix ietf-nst;
    reference
      "RFC XXXX: A Yang Data Model for IETF Network Slice Operation";
  }

  organization
    "IETF Traffic Engineering Architecture and Signaling (TEAS)
     Working Group";
  contact
    "WG Web:  <https://tools.ietf.org/wg/teas/>
     WG List:  <mailto:teas@ietf.org>

     Editor: Bo Wu
          <lana.wubo@huawei.com>
     Editor: Dhruv Dhody
          <dhruv.ietf@gmail.com>
     Editor: Reza Rokui
          <reza.rokui@nokia.com>
     Editor: Tarek Saad
          <tsaad@juniper.net>
     Author: Liuyan Han
          <hanliuyan@chinamobile.com>";
  description
    "This module contains a YANG module for the IETF Network Slice.

        Copyright (c) 2022 IETF Trust and the persons identified as
        authors of the code.  All rights reserved.

        Redistribution and use in source and binary forms, with or
        without modification, is permitted pursuant to, and subject
        to the license terms contained in, the Revised BSD License
        set forth in Section 4.c of the IETF Trust's Legal Provisions
        Relating to IETF Documents
        (https://trustee.ietf.org/license-info).

     This version of this YANG module is part of RFC XXXX; see the
     RFC itself for full legal notices.";

  revision 2022-03-17 {
    description
      "initial version.";
    reference
      "RFC XXXX: A Yang Data Model for IETF Network Slice Operation";
  }

  container network-slices {
    description
      "Containes a list of IETF network slice";
    uses ietf-nst:slice-template;
    list network-slice {
      key "ns-id";
      description
        "A network-slice is identified by a ns-id.";
      uses ietf-nst:ns-properties;
      uses ietf-nst:ns-slo-sle-policy;
      uses ietf-nst:status-params;
      container ns-endpoints {
        description
          "NS Endpoints.";
        list ns-endpoint {
          key "ep-id";
          uses ietf-nst:endpoint;
          description
            "List of endpoints in this slice.";
        }
      }
      uses ietf-nst:ns-connection-groups;

    }
    //ietf-network-slice list
  }
}
